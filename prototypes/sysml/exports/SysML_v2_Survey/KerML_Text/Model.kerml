// ThinkComposer prototype 0.1.0; see companion export report.
    package Survey {
    // source-id: cd605da8-71e4-504a-a4a8-f6797e8e720d
        package Organization {
        // source-id: 04dbd6e2-2122-5ea0-a7ed-c299d919b459
            // UNSUPPORTED_ELEMENT 87666205-667f-5f49-ba37-c94481e4e6a9 PackageImport
            // UNSUPPORTED_ELEMENT b122ee1d-4191-57f5-830a-bbff2203f9cf ExternalReference
        }
        package Structure {
        // source-id: d64df139-1749-5ca4-8095-a396fdd75527
            class PartDefinitionExample {
            // source-id: 56db072c-66a4-5a45-8bb8-ed24417465a4
            }
            datatype AttributeDefinitionExample {
            // source-id: 0d583fcf-a495-5ac6-bd04-50bbbd7d401f
            }
            feature PartUsageExample : PartDefinitionExample {
            // source-id: aef60747-c10b-5fd1-bd87-073e0ebf2323
            }
            feature AttributeUsageExample : AttributeDefinitionExample {
            // source-id: 1413dbd9-cb2e-51f2-9eb9-08c01e89e2b0
            }
        }
        package Interfaces {
        // source-id: 959c7299-8f5c-5eee-8c83-9ff57df3599b
            // UNSUPPORTED_ELEMENT 841ea129-7993-5c56-bf70-3968c98705a7 PortDefinition
            // UNSUPPORTED_ELEMENT 24e2bb58-1f2c-5087-b2c6-924b0949b4cb PortUsage
        }
        package Requirements {
        // source-id: 91b79200-dcee-55a0-ab7e-6ed5f30b1586
            // UNSUPPORTED_ELEMENT 48090672-553d-5030-a935-d32db9c5388e RequirementDefinition
            // UNSUPPORTED_ELEMENT f3741906-7961-55cd-acff-752f5a89a1bd RequirementUsage
        }
        package Behavior {
        // source-id: fadea585-cd2b-5094-b1b9-3525b241ebc5
            // UNSUPPORTED_ELEMENT 4fe11553-969a-5c00-b4bf-0d92e3cb1de2 ActionDefinition
            // UNSUPPORTED_ELEMENT 250a0bd9-fccf-5a1d-bbd8-1b628bcd530c StateDefinition
            // UNSUPPORTED_ELEMENT 70880f69-a2b5-54c0-aa4b-81a7a9ca4f5a ActionUsage
            // UNSUPPORTED_ELEMENT e3c61908-99f1-5914-8685-87e8f30abbae StateUsage
        }
        package Constraints {
        // source-id: a44c0dbd-c94b-5527-a965-cfec44a6ecbe
            // UNSUPPORTED_ELEMENT 6d062d94-4c79-5e7e-887b-6a12670906e1 ConstraintDefinition
            // UNSUPPORTED_ELEMENT a90df57d-b511-5c25-95b6-bd44247e8e32 CalculationDefinition
        }
        package Extensions {
        // source-id: 0a562b61-b326-5548-bfdc-637fb849301c
            // UNSUPPORTED_ELEMENT bc37aa08-7ad1-51c0-951a-e39bbe0a2855 MetadataDefinition
            // UNSUPPORTED_ELEMENT e7e90133-8bfc-5f38-953e-95e04e805cd2 Citation
        }
    }
    // Relationship emitted on its source declaration; check coverage report.
    // Relationship emitted on its source declaration; check coverage report.
    // Relationship emitted on its source declaration; check coverage report.
    // Relationship emitted on its source declaration; check coverage report.
    // Relationship emitted on its source declaration; check coverage report.
    // Relationship emitted on its source declaration; check coverage report.
    // UNSUPPORTED_ELEMENT 4f5ff5f7-f38a-55a0-8484-04638ae03cd0 Trace
