// ThinkComposer prototype 0.1.0; see companion export report.
    package Survey {
    // source-id: 002d6776-b721-55a2-872b-b23262a44cec
        package Organization {
        // source-id: 2957f4e4-91fb-5f47-ab55-c66963d5dd05
            // UNSUPPORTED_ELEMENT 705d9c95-c5fb-5a6c-a816-f9956a5d44ad PackageImport
            // UNSUPPORTED_ELEMENT becbdf90-139a-511c-9a47-2f2c2da1775a ExternalReference
        }
        package Structure {
        // source-id: 1b1663f8-646d-5547-9e0c-e2d1dd87a3d7
            part def PartDefinitionExample {
            // source-id: 9e0aafd8-75e2-5e4b-a3bb-383a7bcdd46d
            }
            attribute def AttributeDefinitionExample {
            // source-id: f42725ff-5850-5030-8fe8-d40f6698cf5b
            }
            part PartUsageExample : PartDefinitionExample {
            // source-id: 8d78c1ee-7019-5af4-8c64-3320d31a3e13
            }
            attribute AttributeUsageExample : AttributeDefinitionExample {
            // source-id: a1b3a9e9-50da-51fa-8881-12d751d62cbe
            }
        }
        package Interfaces {
        // source-id: e86a8e4a-bbcb-51bb-a560-3d27b4834d07
            port def PortDefinitionExample {
            // source-id: b4fbaec6-5ad3-5980-8212-b55f6ad56354
            }
            port PortUsageExample : PortDefinitionExample {
            // source-id: 84e38e8b-b555-5103-a654-aca364d115d1
            }
        }
        package Requirements {
        // source-id: 7be5c6fc-9b97-5106-ac81-4db0b6d6edec
            requirement def RequirementDefinitionExample {
            // source-id: 7ac0b7d4-397f-53cb-b10c-8a06884599d9
            }
            requirement RequirementUsageExample : RequirementDefinitionExample {
            // source-id: 1e1d7dbb-45fb-515d-bcd3-2e85a5591b75
            }
        }
        package Behavior {
        // source-id: ed115fc3-c250-5799-aa3d-927f56c7d3e8
            action def ActionDefinitionExample {
            // source-id: 7186b2c5-cc08-55e5-821a-8f0b1528ba62
            }
            state def StateDefinitionExample {
            // source-id: 0366d35f-95aa-5130-8d94-2afd5a6d70e7
            }
            action ActionUsageExample : ActionDefinitionExample {
            // source-id: 0df20467-5b9f-58e7-a89d-0be0492d0869
            }
            state StateUsageExample : StateDefinitionExample {
            // source-id: 9675156c-d0d2-518e-90e8-4d6724863ecc
            }
        }
        package Constraints {
        // source-id: 4b74b893-005a-5c18-8b26-39aae836caba
            constraint def ConstraintDefinitionExample {
            // source-id: 436ef1af-63e1-5288-9aa7-dcc70bdc9466
            }
            calc def CalculationDefinitionExample {
            // source-id: 86396efb-1713-5e60-86de-9bbf6b4977f0
            }
        }
        package Extensions {
        // source-id: c5083f16-eaea-5da4-a0ba-d6da65558ef0
            metadata def MetadataDefinitionExample {
            // source-id: 63dedb8b-d083-585e-92d8-85f059e27346
            }
            // UNSUPPORTED_ELEMENT 8b4e71cd-65f8-5c4c-8396-05297365a4cf Citation
        }
        package MTConnect {
        // source-id: ac3936e3-74cd-5220-a210-edfa53ba3385
            // UNSUPPORTED_ELEMENT bf07e35e-1bbe-5500-be02-2aad00ddecc5 MTConnectRequirement
        }
    }
    // Relationship emitted on its source declaration; check coverage report.
    // Relationship emitted on its source declaration; check coverage report.
    // Relationship emitted on its source declaration; check coverage report.
    // Relationship emitted on its source declaration; check coverage report.
    // Relationship emitted on its source declaration; check coverage report.
    // Relationship emitted on its source declaration; check coverage report.
    // UNSUPPORTED_ELEMENT e39081ab-d651-59f8-89d9-5acc7c2f8963 Trace
